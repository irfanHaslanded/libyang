module compare {
    yang-version 1.1;
    namespace "http://example.com/compare";

    prefix comp;

    import ietf-inet-types {
        prefix inet;
        reference
          "RFC 6991: Common YANG Data Types";
    }

    leaf a {
        must ". >= ../b" {
            error-message "a >= b";
        }
        type uint16 {
            range 1..3600;
        }
        default 2000;
    }

    leaf b {
        type uint8;
        default 5;
    }
}
